module sonic-mld-snooping {
	namespace "http://github.com/sonic-net/sonic-mld-snooping";
	prefix smlds;
	yang-version 1.1;

	import ietf-inet-types {
		prefix inet;
	}

	organization
		"SONIC";

	contact
		"SONiC";

	description
		"SONIC MLD SNOOPING";

	revision 2025-11-14 {
		description
			"Initial revision.";
	}

	container sonic-mld-snooping {

		container MLD_L2MC_STATIC_GROUP {

			list MLD_L2MC_STATIC_GROUP_LIST {
				key "vlan-name group-addr";

				leaf vlan-name {
					type string;
				}

				leaf group-addr {
					type inet:ipv6-address;
				}

				leaf-list static-members {
					type string;
					description "List of interfaces/portchannels for the multicast group.";
				}
			}			
		}

		container MLD_L2MC_STATIC_MEMBER {

			list MLD_L2MC_STATIC_MEMBER_LIST {

				key "vlan-name group-addr out-intf";

				leaf vlan-name {
					type string;	
				}

				leaf group-addr {
					type inet:ipv6-address;
				}

				leaf out-intf {
					type string;
				}
				leaf port {
					type string;
				}			
			}
		}

		container MLD_L2MC_MROUTER {

			list MLD_L2MC_MROUTER_LIST {

				key "vlan-name mrouter-intf";

				leaf vlan-name {
					type string;
				}

				leaf mrouter-intf {
					type string;
				}

				leaf mrouter_port {
					type string;
				}			
			}		
		}

		container MLD_L2MC {		

			list MLD_L2MC_LIST {
				key "vlan-name";

				leaf vlan-name {
					type string;
				} 

				leaf enabled {
					type boolean;
					default false;
				}

				leaf querier {
					type boolean;
					default false;
				}

				leaf fast-leave {
					type boolean;	
					default false;							
				}			

				leaf version {
					type uint8 {
						range "1..2"{
							error-message "Invalid MLD Snooping version.";
						}
					}
					default 2;
				}

				leaf query-interval {
					must "current() > ../query-max-response-time" {
						error-message "Invalid MLD Snooping query interval value.";
					}

					type uint32 {
						range "1..18000" {
							error-message "Invalid MLD Snooping Query Interval.";
						}
					}
					default 125;
				}

				leaf last-member-query-interval {
					type uint32 {
						range "100..25500"{
							error-message "Invalid MLD Snooping Last Member Query Interval.";
						}
					}
					default 1000;
				}

				leaf query-max-response-time {
					must "current() < ../query-interval" {
						error-message "Invalid MLD Snooping query interval value.";
					}				
					type uint16 {
						range "1..25"{
							error-message "Invalid MLD Snooping Query Max Response Time.";
						}
					}
					default 10;
				}				
			}		
		}
	}
}
